Dim quelle As String = "C:\Users\kw\Documents\ABEP_Koppeltest\CAD\Aufhängung\Zeichnungen"       ' Ordner mit den .dxf
Dim ziel As String = "C:\Users\kw\Documents\ABEP_Koppeltest\CAD\Aufhängung\Zeichnungen\"
Dim format As String = ".idw"                           ' oder ".dwg"
System.IO.Directory.CreateDirectory(ziel)

Dim files() As String = System.IO.Directory.GetFiles(quelle, "*.dxf")
Array.Sort(files)

Dim ok As Integer = 0
Dim log As String = ""
For Each f As String In files
    Dim name As String = System.IO.Path.GetFileNameWithoutExtension(f)
    Try
        Dim d As Document = ThisApplication.Documents.Open(f, True)
        d.SaveAs(ziel & name & format, False)
        d.Close(True)
        ok += 1
    Catch ex As Exception
        log &= name & ": " & ex.Message & vbCrLf
    End Try
Next

MessageBox.Show(ok & " von " & files.Length & " konvertiert nach " & ziel & vbCrLf & vbCrLf & log)
